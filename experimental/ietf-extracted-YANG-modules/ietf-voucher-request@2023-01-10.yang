module ietf-voucher-request {
  yang-version 1.1;
  namespace "urn:ietf:params:xml:ns:yang:ietf-voucher-request";
  prefix vcr;

  import ietf-yang-structure-ext {
    prefix sx;
  }
  import ietf-voucher {
    prefix vch;
    description
      "This module defines the format for a voucher,
       which is produced by a pledge's manufacturer or
       delegate (MASA) to securely assign a pledge to
       an 'owner', so that the pledge may establish a secure
       connection to the owner's network infrastructure";
    reference
      "RFC XXXX: Voucher Artifact for
       Bootstrapping Protocols";
  }

  organization
    "IETF ANIMA Working Group";
  contact
    "WG Web:   <https://datatracker.ietf.org/wg/anima/>
     WG List:  <mailto:anima@ietf.org>
     Author:   Kent Watsen
               <mailto:kent+ietf@watsen.net>
     Author:   Michael Richardson
               <mailto:mcr+ietf@sandelman.ca>
     Author:   Max Pritikin
               <mailto:pritikin@cisco.com>
     Author:   Toerless Eckert
               <mailto:tte@cs.fau.de>
     Author:   Qiufang Ma
               <mailto:maqiufang1@huawei.com>";
  description
    "This module defines the format for a voucher request.
     It is a superset of the voucher itself.
     It provides content to the MASA for consideration
     during a voucher request.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

      Copyright (c) 2024 IETF Trust and the persons identified as
      authors of the code.  All rights reserved.

      Redistribution and use in source and binary forms, with or
      without modification, is permitted pursuant to, and subject to
      the license terms contained in, the Revised BSD License set
      forth in Section 4.c of the IETF Trust's Legal Provisions
      Relating to IETF Documents
      (https://trustee.ietf.org/license-info).

      This version of this YANG module is part of RFC XXXX
      (https://www.rfc-editor.org/info/rfcXXXX); see the RFC itself
      for full legal notices.

     RFCEDITOR: please replace XXXX with the RFC number assigned.

      The key words 'MUST', 'MUST NOT', 'REQUIRED', 'SHALL', 'SHALL
      NOT', 'SHOULD', 'SHOULD NOT', 'RECOMMENDED', 'NOT RECOMMENDED',
      'MAY', and 'OPTIONAL' in this document are to be interpreted as
      described in BCP 14 (RFC 2119) (RFC 8174) when, and only when,
      they appear in all capitals, as shown here.";

  revision 2023-01-10 {
    description
      "Initial version";
    reference
      "RFC XXXX: Bootstrapping Remote Secure Key Infrastructure";
  }

  grouping voucher-request-grouping {
    description
      "Grouping to allow reuse/extensions in future work.";
    uses vch:voucher-artifact-grouping {
      refine "last-renewal-date" {
        description
          "A last-renewal-date field
           is not valid in a voucher request, and
           any occurrence MUST be ignored";
      }
      refine "domain-cert-revocation-checks" {
        description
          "The domain-cert-revocation-checks field
           is not valid in a voucher request, and
           any occurrence MUST be ignored";
      }
      refine "assertion" {
        description
          "Any assertion included in registrar voucher
           requests SHOULD be ignored by the MASA.";
      }
    }
    leaf prior-signed-voucher-request {
      type binary;
      description
        "If it is necessary to change a voucher, or re-sign and
         forward a voucher request that was previously provided \
                                                              along a
         protocol path, then the previously signed voucher SHOULD
         be included in this field.

         For example, a pledge might sign a voucher request
         with a proximity-registrar-cert, and the registrar
         then includes it as the prior-signed-voucher-request
         field.  This is a simple mechanism for a chain of
         trusted parties to change a voucher request, while
         maintaining the prior signature information.

         The Registrar and MASA MAY examine the prior signed
         voucher information for the
         purposes of policy decisions. The MASA SHOULD remove all
         prior-signed-voucher-request information when
         signing a voucher for imprinting so as to minimize
         the final voucher size.";
    }
    leaf proximity-registrar-cert {
      type binary;
      description
        "An X.509 v3 certificate structure as specified by
         RFC 5280, Section 4 encoded using the ASN.1
         distinguished encoding rules (DER), as specified
         in [ITU.X690.1994].

         The first certificate in the Registrar TLS server
         certificate_list sequence  (the end-entity TLS
         certificate, see [RFC8446]) presented by the Registrar
         to the Pledge.
         This MUST be populated in a Pledge's voucher request
         when a proximity assertion is requested.";
    }
    leaf proximity-registrar-pubk {
      type binary;
      description
        "The proximity-registrar-pubk replaces
         the proximity-registrar-cert in constrained uses of
         the voucher-request.
         The proximity-registrar-pubk is the
         Raw Public Key of the Registrar. This field is encoded
         as specified in RFC7250, section 3.
         The ECDSA algorithm MUST be supported.
         The EdDSA algorithm as specified in
         draft-ietf-tls-rfc4492bis-17 SHOULD be supported.
         Support for the DSA algorithm is not recommended.
         Support for the RSA algorithm is a MAY, but due to
         size is discouraged.";
    }
    leaf proximity-registrar-pubk-sha256 {
      type binary;
      description
        "The proximity-registrar-pubk-sha256
         is an alternative to both
         proximity-registrar-pubk and pinned-domain-cert.
         In many cases the public key of the domain has already
         been transmitted during the key agreement protocol,
         and it is wasteful to transmit the public key another
         two times.
         The use of a hash of public key info, at 32-bytes for
         sha256 is a significant savings compared to an RSA
         public key, but is only a minor savings compared to
         a 256-bit ECDSA public-key.
         Algorithm agility is provided by extensions to this
         specification which may define a new leaf for another
         hash type.";
    }
    leaf agent-signed-data {
      type binary;
      description
        "The agent-signed-data field contains a data artifact \
                                                             provided
         by the Registrar-Agent to the Pledge for inclusion into the
         voucher request.

         This artifact is signed by the Registrar-Agent and contains
         data, which can be verified by the pledge and the registrar.
         This data contains the pledge's serial-number and a created\
                                                                  -on
         information of the agent-signed-data.

         The format is intentionally defined as binary to allow
         the document using this leaf to determine the encoding.";
    }
    leaf agent-provided-proximity-registrar-cert {
      type binary;
      description
        "An X.509 v3 certificate structure, as specified by
         RFC 5280, Section 4, encoded using the ASN.1
         distinguished encoding rules (DER), as specified
         in ITU X.690.
         The first certificate in the registrar TLS server
         certificate_list sequence (the end-entity TLS
         certificate; see RFC 8446) presented by the
         registrar to the registrar-agent and provided to
         the pledge.
         This MUST be populated in a pledge's voucher-request
         when an agent-proximity assertion is requested.";
      reference
        "ITU X.690: Information Technology - ASN.1 encoding
         rules: Specification of Basic Encoding Rules (BER),
         Canonical Encoding Rules (CER) and Distinguished
         Encoding Rules (DER)
         RFC 5280: Internet X.509 Public Key Infrastructure
         Certificate and Certificate Revocation List (CRL)
         Profile
         RFC 8446: The Transport Layer Security (TLS)
         Protocol Version 1.3";
    }
    leaf agent-sign-cert {
      type binary;
      description
        "An X.509 v3 certificate structure, as specified by
         RFC 5280, Section 4, encoded using the ASN.1
         distinguished encoding rules (DER), as specified
         in ITU X.690.
         This certificate can be used by the pledge,
         the registrar, and the MASA to verify the signature
         of agent-signed-data. It is an optional component
         for the pledge-voucher request.
         This MUST be populated in a registrar's
         voucher-request when an agent-proximity assertion
         is requested.";
      reference
        "ITU X.690: Information Technology - ASN.1 encoding
         rules: Specification of Basic Encoding Rules (BER),
         Canonical Encoding Rules (CER) and Distinguished
         Encoding Rules (DER)
         RFC 5280: Internet X.509 Public Key Infrastructure
         Certificate and Certificate Revocation List (CRL)
         Profile";
    }
  }

  // Top-level statement
  // Called "voucher" to match RFC8995
  sx:structure voucher {
    uses voucher-request-grouping;
  }
}
