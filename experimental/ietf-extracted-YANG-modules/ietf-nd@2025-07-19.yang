module ietf-nd {
  yang-version 1.1;
  namespace
    "urn:ietf:params:xml:ns:yang:ietf-nd";
  prefix nd;

  import ietf-inet-types {
    prefix inet;
  }
  import ietf-yang-types {
    prefix yang;
    reference
      "RFC 6991: Common YANG Data Types";
  }
  import ietf-interfaces {
    prefix if;
    reference
      "RFC 8343: A Yang Data Model for Interface Management";
  }
  import ietf-ip {
    prefix ip;
    reference
      "RFC 8344: A Yang Data Model for IP Management";
  }

  organization
    "IETF IPv6 Maintenance Working Group (6man)";
  contact
    "WG Web:  <https://datatracker.ietf.org/wg/6man/>
     WG List: <mailto: 6man@ietf.org>

     Author:  Fan Zhang
              <zhangf52@chinatelecom.cn>
     Author:  Yongqing Zhu
              <zhuyq8@chinatelecom.cn>
     Author:  Bo Wu
              <lana.wubo@huawei.com>
     Author:  Jiayuan Hu
              <hujy5@chinatelecom.cn>";
  description
    "This YANG module defines a YANG data model to configure and manage
     IPv6 Neighbor Discovery (ND) and related functions, including
     IPv6 address resolution, redirect function, proxy Neighbor
     Advertisement, Neighbor Unreachability Detection (NUD), Duplicate
     Address Detection (DAD), SEcure Neighbor Discovery (SEND), and
     Secure ND Proxy.

     The model is based on YANG 1.1 as defined in RFC 7950 and
     conforms to Network Management Datastore Architecture (NMDA)
     as defined in RFC 8342.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  reference
    "RFC4861: Neighbor Discovery for IP version 6 (IPv6)
     RFC4862: IPv6 Stateless Address Autoconfiguration";

  revision 2025-07-19 {
    description
      "Init revision";
    reference
      "RFC XXXX: YANG Data Model for IPv6 Neighbor Discovery";
  }

  /* Data nodes */

  container nd {
    description
      "Global parameters for IPv6 ND.";
    leaf stale-timeout {
      type uint32;
      units "second";
      description
        "The global timeout for Neighbor Cache entry in the STALE
         state.";
      reference
        "RFC4861: Neighbor Discovery for IP version 6 (IPv6)
                  Section 5.3";
    }
    container secure-nd {
      description
        "Global parameters for SEcure Neighbor Discovery (SEND).";
      leaf cga-flag {
        type boolean;
        description
          "Flag to indicate whether the node is using CGA.";
      }
      leaf minbits {
        type uint32;
        default "1024";
        description
          "The minimum acceptable key length for public keys used
           in the generation of CGAs.";
      }
      leaf keypair {
        type string;
        description
          "The public-private key pair used for RSA signatures.";
      }
      container RSA-signature-option-reception {
        description
          "Parameter for the node that support the reception of the RSA
           Signature options.";
        leaf ns-authorization-method {
          type enumeration {
            enum trust-anchor {
              description
                "The sender's authority is verified via trust anchor.";
            }
            enum cga {
              description
                "The sender's authority is verified via CGA.";
            }
            enum trust-anchor-and-cga {
              description
                "Both trust anchor and CGA verification are required.";
            }
            enum trust-anchor-or-cga {
              description
                "Either trust anchor or CGA verification is required.";
            }
          }
          description
            "The method to verify the authority of the sender of NS
             messages.";
        }
        leaf na-authorization-method {
          type enumeration {
            enum trust-anchor {
              description
                "The sender's authority is verified via trust anchor.";
            }
            enum cga {
              description
                "The sender's authority is verified via CGA.";
            }
            enum trust-anchor-and-cga {
              description
                "Both trust anchor and CGA verification are required.";
            }
            enum trust-anchor-or-cga {
              description
                "Either trust anchor or CGA verification is required.";
            }
          }
          description
            "The method to verify the authority of the sender of NA
             messages.";
        }
        leaf rs-authorization-method {
          type enumeration {
            enum trust-anchor {
              description
                "The sender's authority is verified via trust anchor.";
            }
            enum cga {
              description
                "The sender's authority is verified via CGA.";
            }
            enum trust-anchor-and-cga {
              description
                "Both trust anchor and CGA verification are required.";
            }
            enum trust-anchor-or-cga {
              description
                "Either trust anchor or CGA verification is required.";
            }
          }
          description
            "The method to verify the authority of the sender of RS
             messages.";
        }
        leaf ra-authorization-method {
          type enumeration {
            enum trust-anchor {
              description
                "The sender's authority is verified via trust anchor.";
            }
            enum cga {
              description
                "The sender's authority is verified via CGA.";
            }
            enum trust-anchor-and-cga {
              description
                "Both trust anchor and CGA verification are required.";
            }
            enum trust-anchor-or-cga {
              description
                "Either trust anchor or CGA verification is required.";
            }
          }
          description
            "The method to verify the authority of the sender of RA
             messages.";
        }
        leaf redirect-authorization-method {
          type enumeration {
            enum trust-anchor {
              description
                "The sender's authority is verified via trust anchor.";
            }
            enum cga {
              description
                "The sender's authority is verified via CGA.";
            }
            enum trust-anchor-and-cga {
              description
                "Both trust anchor and CGA verification are required.";
            }
            enum trust-anchor-or-cga {
              description
                "Either trust anchor or CGA verification is required.";
            }
          }
          description
            "The method to verify the authority of the sender of
             Redirect messages.";
        }
      }
      container timestamp {
        description
          "Parameters of Timestamp option.";
        leaf timestamp-delta {
          type uint32;
          units "second";
          default "300";
          description
            "The allowed timestamp Delta value.";
        }
        leaf timestamp-fuzz {
          type uint32;
          units "second";
          default "1";
          description
            "The 'fuzz factor' for comparisons.";
        }
        leaf timestamp-drift {
          type uint8;
          units "percent";
          default "1";
          description
            "The allowed clock drift parameter.";
        }
      }
      reference
        "RFC3971: SEcure Neighbor Discovery (SEND)";
    }
  }

  augment "/if:interfaces/if:interface/ip:ipv6" {
    description
      "Augments interface configuration and state data with
       parameters of IPv6 ND.";
    container nd {
      description
        "Parameters of IPv6 ND.";
      leaf dynamic-discovery {
        type boolean;
        default "true";
        description
          "Controls whether dynamic link-layer address resolution
           for IPv6 on the interface is enabled or disabled.
            true -  dynamic link-layer address resolution based on
                    IPv6 ND is enabled,
            false - dynamic link-layer address resolution based on
                    IPv6 ND is disabled.";
        reference
          "RFC4861: Neighbor Discovery for IP version 6 (IPv6)
                    Section 7.2";
      }
      leaf nud {
        type boolean;
        default "true";
        description
          "Controls whether Neighbor Unreachability Detection (NUD)
           on the interface is enabled or disabled.
            true -  NUD is enabled,
            false - NUD is disabled.";
        reference
          "RFC4861: Neighbor Discovery for IP version 6 (IPv6)
                    Section 7.3";
      }
      leaf reachable-time {
        type uint32 {
          range "0..3600000";
        }
        units "millisecond";
        description
          "The time to confirm a neighbor's reachability for NUD.";
        reference
          "RFC4861: Neighbor Discovery for IP version 6 (IPv6)
                    - ReachableTime";
      }
      leaf ns-interval {
        type uint32;
        units "milliseconds";
        description
          "The interval of retransmitting Neighbor Solicitations to a
           neighbor for address resolution, NUD, or DAD.";
        reference
          "RFC4861: Neighbor Discovery for IP version 6 (IPv6)
                    Section 7.3.3";
      }
      leaf stale-timeout {
        type uint32;
        units "second";
        description
          "The timeout for Neighbor Cache entry in the STALE state on
           the interface.";
        reference
          "RFC4861: Neighbor Discovery for IP version 6 (IPv6)
                    Section 5.3";
      }
      leaf redirect {
        type boolean;
        default "false";
        description
          "Controls whether sending of ICMP Redirect messages
           on the interface is enabled or disabled.
            true -  Sending of ICMP Redirect messages is enabled,
            false - Sending of ICMP Redirect messages is disabled.";
        reference
          "RFC4861: Neighbor Discovery for IP version 6 (IPv6)
                    Section 8";
      }
      container proxy-na {
        description
          "Parameters of proxy Neighbor Advertisements.";
        leaf inter-vlan-proxy {
          type boolean;
          default "false";
          description
            "Controls whether the router proxies for hosts in the
             same subnet with different VLANs";
        }
        leaf all-proxy {
          type boolean;
          default "false";
          description
            "Controls whether the router proxies for all hosts,
             that is, responds unconditionally to Neighbor
             Solicitation with its own Neighbor Advertisement.";
        }
        reference
          "RFC4861: Neighbor Discovery for IP version 6 (IPv6)
                    Section 7.2.8";
      }
      container secure-nd {
        description
          "Parameters of SEcure Neighbor Discovery (SEND).";
        leaf cga-flag {
          type boolean;
          description
            "Flag to indicate whether the interface is using CGA.";
        }
        leaf modifier {
          type inet:ipv6-address;
          description
            "Modifier for CGA.";
        }
        reference
          "RFC3971: SEcure Neighbor Discovery (SEND)";
      }
      leaf secure-proxy-nd {
        type boolean;
        default "false";
        description
          "Controls whether Secure ND Proxy is enabled or disabled.";
        reference
          "RFC6496: Secure Proxy ND Support for SEcure Neighbor
           Discovery (SEND)";
      }
      container statistics {
        config false;
        description
          "A collection of interface-related statistics about IPv6
           ND messages.";
        leaf in-ns-pkts {
          type yang:counter32;
          description
            "The number of received Neighbor Solicitation packets.";
        }
        leaf in-na-pkts {
          type yang:counter32;
          description
            "The number of received Neighbor Advertisement packets.";
        }
        leaf in-rs-pkts {
          type yang:counter32;
          description
            "The number of received Router Solicitation packets.";
        }
        leaf in-ra-pkts {
          type yang:counter32;
          description
            "The number of received Router Advertisement packets.";
        }
        leaf in-redirect-pkts {
          type yang:counter32;
          description
            "The number of received Redirect packets.";
        }
        leaf out-ns-pkts {
          type yang:counter32;
          description
            "The number of sent Neighbor Solicitation packets.";
        }
        leaf out-na-pkts {
          type yang:counter32;
          description
            "The number of sent Neighbor Advertisement packets.";
        }
        leaf out-rs-pkts {
          type yang:counter32;
          description
            "The number of sent Router Solicitation packets.";
        }
        leaf out-ra-pkts {
          type yang:counter32;
          description
            "The number of sent Router Advertisement packets.";
        }
        leaf out-redirect-pkts {
          type yang:counter32;
          description
            "The number of sent Redirect packets.";
        }
      }
    }
  }

  augment "/if:interfaces/if:interface/ip:ipv6/ip:neighbor" {
    description
      "Augments IPv6 neighbor list with parameters of IPv6 address
       resolution based on IPv6 ND.";
    leaf age {
      type uint32;
      units "milliseconds";
      config false;
      description
        "The time that has passed since receipt of the last
         reachability confirmation for the neighbor.";
      reference
        "RFC4861: Neighbor Discovery for IP version 6 (IPv6)
                  Section 5.1";
    }
  }
}
