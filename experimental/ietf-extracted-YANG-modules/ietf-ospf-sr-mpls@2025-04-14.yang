module ietf-ospf-sr-mpls {
  yang-version 1.1;
  namespace "urn:ietf:params:xml:ns:yang:ietf-ospf-sr-mpls";
  prefix ospf-sr-mpls;

  import ietf-inet-types {
    prefix inet;
    reference
      "RFC 6991: Common YANG Data Types";
  }
  import ietf-routing-types {
    prefix rt-types;
    reference
      "RFC 8294: Common YANG Data Types for the Routing Area";
  }
  import iana-routing-types {
    prefix iana-rt-types;
    reference
      "RFC 8294: Common YANG Data Types for the Routing Area";
  }
  import ietf-routing {
    prefix rt;
    reference
      "RFC 8349: A YANG Data Model for Routing
                 Management (NMDA Version)";
  }
  import ietf-segment-routing-common {
    prefix sr-cmn;
    reference
      "RFC 9020: YANG Data Model for Segment Routing";
  }
  import ietf-segment-routing-mpls {
    prefix sr-mpls;
    reference
      "RFC 9020: YANG Data Model for Segment Routing";
  }
  import ietf-ospf {
    prefix ospf;
    reference
      "RFC 9129: YANG Data Model for the OSPF Protocol";
  }
  import ietf-ospfv3-extended-lsa {
    prefix ospfv3-e-lsa;
    reference
      "RFC 9587: YANG Data Model for OSPFv3 Extended LSAs";
  }

  organization
    "IETF LSR - Link State Routing Working Group";
  contact
    "WG Web:   <https://datatracker.ietf.org/wg/lsr/>
     WG List:  <mailto:lsr@ietf.org>

     Author:   Yingzhen Qu
               <mailto:yingzhen.ietf@gmail.com>
     Author:   Acee Lindem
               <mailto:acee.ietf@gmail.com>
     Author:   Derek Yeung
               <mailto:derek@arrcus.com>
     Author:   Jeffrey Zhang
               <mailto:zzhang@juniper.net>
     Author:   Ing-Wher Chen
               <mailto:ingwherchen@mitre.org>";
  description
    "This YANG module defines the generic configuration
     and operational state for OSPF Segment Routing (SR).

     Copyright (c) 2025 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry
     (https://www.iana.org/assignments/yang-parameters).

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

      This version of this YANG module is part of RFC XXXX; see
     the RFC itself for full legal notices.";

  // RFC Ed.: Replace XXXX with actual RFC number and remove
  // this note

  revision 2025-04-14 {
    description
      "Initial revision.";
    reference
      "RFC XXXX: A YANG Data Model for OSPF Segment Routing for
       over MPLS Data Plane";
  }

  // RFC Ed.: Replace XXXX with actual RFC number.
  // Also, replace '2025-04-14' with the module publication date
  // in the format (YYYY-MM-DD) and remove this note.

  feature remote-lfa-sr {
    description
      "Enhance rLFA to use SR path.";
    reference
      "RFC 8102: Remote-LFA Node Protection and Manageability";
  }

  feature ti-lfa {
    description
      "Topology-Independent Loop-Free Alternate (TI-LFA)
       computation using segment routing.";
    reference
      "draft-ietf-rtgwg-segment-routing-ti-lfa:
       Topology-Independent Fast Reroute using Segment Routing";
  }

  identity prefix-sid-flag {
    description
      "Base identity for prefix SID sub-TLV flags.";
    reference
      "RFC 8665: OSPF Extensions for Segment Routing, Section 5
       RFC 8666: OSPFv3 Extensions for Segment Routing, Section 6";
  }

  identity np-flag {
    base prefix-sid-flag;
    description
      "No-PHP flag.";
    reference
      "RFC 8665: OSPF Extensions for Segment Routing, Section 5
       RFC 8666: OSPFv3 Extensions for Segment Routing, Section 6";
  }

  identity m-flag {
    base prefix-sid-flag;
    description
      "Mapping server flag.";
    reference
      "RFC 8665: OSPF Extensions for Segment Routing, Section 5
       RFC 8666: OSPFv3 Extensions for Segment Routing, Section 6";
  }

  identity e-flag {
    base prefix-sid-flag;
    description
      "Explicit-NULL flag.";
    reference
      "RFC 8665: OSPF Extensions for Segment Routing, Section 5
       RFC 8666: OSPFv3 Extensions for Segment Routing, Section 6";
  }

  identity v-flag {
    base prefix-sid-flag;
    description
      "Value/Index flag.";
    reference
      "RFC 8665: OSPF Extensions for Segment Routing, Section 5
       RFC 8666: OSPFv3 Extensions for Segment Routing, Section 6";
  }

  identity l-flag {
    base prefix-sid-flag;
    description
      "Local flag.";
    reference
      "RFC 8665: OSPF Extensions for Segment Routing, Section 5
       RFC 8666: OSPFv3 Extensions for Segment Routing, Section 6";
  }

  identity extended-prefix-range-flag {
    description
      "Base identity for extended prefix range TLV flags.";
    reference
      "RFC 8665: OSPF Extensions for Segment Routing, Section 4
       RFC 8666: OSPFv3 Extensions for Segment Routing, Section 5";
  }

  identity ia-flag {
    base extended-prefix-range-flag;
    description
      "Inter-Area flag.";
    reference
      "RFC 8665: OSPF Extensions for Segment Routing, Section 4
       RFC 8666: OSPFv3 Extensions for Segment Routing, Section 5";
  }

  identity adj-sid-flag {
    description
      "Base identity for Adj-SID sub-TLV flags.";
    reference
      "RFC 8665: OSPF Extensions for Segment Routing, Section 6
       RFC 8666: OSPFv3 Extensions for Segment Routing, Section 7";
  }

  identity b-flag {
    base adj-sid-flag;
    description
      "Backup flag.";
    reference
      "RFC 8665: OSPF Extensions for Segment Routing, Section 6
       RFC 8666: OSPFv3 Extensions for Segment Routing, Section 7";
  }

  identity vi-flag {
    base adj-sid-flag;
    description
      "Value/Index flag - corresponds to V-Flag in references.";
    reference
      "RFC 8665: OSPF Extensions for Segment Routing, Section 6
       RFC 8666: OSPFv3 Extensions for Segment Routing, Section 7";
  }

  identity lg-flag {
    base adj-sid-flag;
    description
      "Local/Global flag - corresponds to L-flag in references.";
    reference
      "RFC 8665: OSPF Extensions for Segment Routing, Section 6
       RFC 8666: OSPFv3 Extensions for Segment Routing, Section 7";
  }

  identity g-flag {
    base adj-sid-flag;
    description
      "Group flag.";
    reference
      "RFC 8665: OSPF Extensions for Segment Routing, Section 6
       RFC 8666: OSPFv3 Extensions for Segment Routing, Section 7";
  }

  identity p-flag {
    base adj-sid-flag;
    description
      "Persistent flag.";
    reference
      "RFC 8665: OSPF Extensions for Segment Routing, Section 6
       RFC 8666: OSPFv3 Extensions for Segment Routing, Section 7";
  }

  /* Groupings */

  grouping sid-tlv-encoding {
    description
      "SID TLV Encoding -  20-bit label or 32-bit SID index whose
       interpretation is dependent on the TLV length (3 for an
       MPLS label or 4 for a 32-bit value)  or the TLV V-Flag and
       L-Flag settings:

        If the  V-Flag is set to 0 and L-Flag is set to 0:
        The SID/Index/Label field is a 4-octet index defining
        the offset in the SID/Label space advertised by this
        router.

        If V-Flag is set to 1 and L-Flag is set to 1: The
        ID/Index/Label field is a 3-octet local label where the
        20 rightmost bits are used for encoding the label value.";
    reference
      "RFC 8665: OSPF Extensions for Segment Routing, Section 5
       RFC 8666: OSPFv3 Extensions for Segment Routing, Section 3";
    choice sid {
      case sid-label {
        leaf label-value {
          type uint32 {
            range "0 .. 1048575";
          }
          description
            "A 20-bit MPLS Label";
        }
      }
      case sid-index {
        leaf index-value {
          type uint32;
          description
            "Index into a label space advertised by this router.";
        }
      }
      description
        "Choice of either a 20-bit MPLS label or 32-bit index into
         an advertised label space.";
    }
  }

  grouping sid-sub-tlv {
    description
      "SID/Label sub-TLV grouping.";
    reference
      "RFC 8665: OSPF Extensions for Segment Routing
       (Section 2.1)";
    container sid-sub-tlv {
      description
        "Used to advertise the SID/Label associated with a
         prefix or adjacency.";
      leaf length {
        type uint16;
        description
          "Length of the SID value. YANG model specification
           is necessary since it dictates the semantics of the
           SID.";
      }
      uses sid-tlv-encoding;
    }
  }

  grouping ospfv2-prefix-sid-sub-tlvs {
    description
      "OSPFv2 Prefix Segment ID (SID) sub-TLVs.";
    reference
      "RFC 8665: OSPF Extensions for Segment Routing
        (Section 5)";
    container prefix-sid-sub-tlvs {
      description
        "Prefix SID sub-TLV.";
      list prefix-sid-sub-tlv {
        description
          "Prefix SID sub-TLV.";
        container prefix-sid-flags {
          leaf-list flag {
            type identityref {
              base prefix-sid-flag;
            }
            description
              "Prefix SID Sub-TLV flags.";
          }
          description
            "Segment Identifier (SID) Flags.";
        }
        leaf mt-id {
          type uint8 {
            range "0 .. 127";
          }
          description
            "Multi-topology ID. Topologies range from 0-127 and
             return of any other value would indicate an error.";
          reference
            "RFC 4915: Multi-Topology (MT) Routing in OSPF";
        }
        leaf algorithm {
          type identityref {
            base sr-cmn:prefix-sid-algorithm;
          }
          description
            "Algorithm associated with the prefix-SID.";
        }
        uses sid-tlv-encoding;
      }
    }
  }

  grouping ospfv2-extended-prefix-range-tlvs {
    description
      "OSPFv2 Extended prefix range TLV grouping.";
    reference
      "RFC 8665: OSPF Extensions for Segment Routing
       (Section 4)";
    container extended-prefix-range-tlvs {
      description
        "List of range of prefixes.";
      list extended-prefix-range-tlv {
        description
          "Range of prefixes.";
        leaf prefix-length {
          type uint8;
          description
            "Length of prefix in bits.";
        }
        leaf af {
          type iana-rt-types:address-family;
          description
            "Address family for the prefix.";
        }
        leaf range-size {
          type uint16;
          description
            "Number of prefixes covered by the
             advertisement.";
        }
        container extended-prefix-range-flags {
          leaf-list flag {
            type identityref {
              base extended-prefix-range-flag;
            }
            description
              "Extended prefix range TLV flags.";
          }
          description
            "Extended Prefix Range TLV flags.";
        }
        leaf prefix {
          type inet:ipv4-prefix;
          description
            "IPv4 prefix.";
        }
        uses ospfv2-prefix-sid-sub-tlvs;
        uses ospf:unknown-tlvs;
      }
    }
  }

  grouping ospfv2-adj-sid-sub-tlvs {
    description
      "OSPFv2 Adj-SID sub-TLV grouping.";
    container adj-sid-sub-tlvs {
      description
        "Adj-SID optional sub-TLVs.";
      list adj-sid-sub-tlv {
        description
          "List of Adj-SID sub-TLVs.";
        container adj-sid-flags {
          leaf-list flag {
            type identityref {
              base adj-sid-flag;
            }
            description
              "Adj-SID sub-TLV flags.";
          }
          description
            "Adj-SID sub-TLV flags.";
        }
        leaf mt-id {
          type uint8 {
            range "0 .. 127";
          }
          description
            "Multi-topology ID. Topologies range from 0-127 and
             return of any other value would indicate an error.";
          reference
            "RFC 4915: Multi-Topology (MT) Routing in OSPF";
        }
        leaf weight {
          type uint8;
          description
            "Weight used for load-balancing.";
        }
        uses sid-tlv-encoding;
      }
    }
  }

  grouping ospfv2-lan-adj-sid-sub-tlvs {
    description
      "OSPFv2 LAN Adj-SID sub-TLV grouping.";
    container lan-adj-sid-sub-tlvs {
      description
        "LAN Adj-SID optional sub-TLVs.";
      reference
        "RFC 8665: OSPF Extensions for Segment Routing
         (Section 6)";
      list lan-adj-sid-sub-tlv {
        description
          "List of LAN Adj-SID sub-TLVs.";
        container lan-adj-sid-flags {
          leaf-list flag {
            type identityref {
              base adj-sid-flag;
            }
            description
              "LAN Adj-SID sub-TLV flags.";
          }
          description
            "LAN Adj-SID sub-TLV flags.";
        }
        leaf mt-id {
          type uint8 {
            range "0 .. 127";
          }
          description
            "Multi-topology ID. Topologies range from 0-127 and
             return of any other value would indicate an error.";
          reference
            "RFC 4915: Multi-Topology (MT) Routing in OSPF";
        }
        leaf weight {
          type uint8;
          description
            "Weight used for load-balancing.";
        }
        leaf neighbor-router-id {
          type rt-types:router-id;
          description
            "Neighbor router ID.";
        }
        uses sid-tlv-encoding;
      }
    }
  }

  grouping sr-algorithm-tlv {
    description
      "SR algorithm TLV grouping.";
    reference
      "RFC 8665: OSPF Extensions for Segment Routing
       (Section 3.1)";
    container sr-algorithm-tlv {
      description
        "All SR algorithm TLVs.";
      leaf-list sr-algorithm {
        type identityref {
          base sr-cmn:prefix-sid-algorithm;
        }
        description
          "Segment Routing (SR) algorithms that the router is
           currently using.";
      }
    }
  }

  grouping sid-range-tlvs {
    description
      "SID Range TLV grouping.";
    reference
      "RFC 8665: OSPF Extensions for Segment Routing
       (Section 3.2)";
    container sid-range-tlvs {
      description
        "List of SID range TLVs.";
      list sid-range-tlv {
        description
          "SID range TLV.";
        leaf range-size {
          type rt-types:uint24;
          description
            "SID range.";
        }
        uses sid-sub-tlv;
      }
    }
  }

  grouping local-block-tlvs {
    description
      "The SR local block TLV contains the
       range of labels reserved for local SIDs.";
    reference
      "RFC 8665: OSPF Extensions for Segment Routing
       (Section 3.3)";
    container local-block-tlvs {
      description
        "List of SRLB TLVs.";
      list local-block-tlv {
        description
          "SRLB TLV.";
        leaf range-size {
          type rt-types:uint24;
          description
            "SID range. The return of a zero value would indicate
             an error.";
        }
        uses sid-sub-tlv;
      }
    }
  }

  grouping srms-preference-tlv {
    description
      "The SR Mapping Server (SRMS) preference TLV is
       used to advertise a preference associated with
       the node that acts as an SR Mapping Server. SR
       Mapping Server advertisements with a higher
       preference value are preferred over those with
       a lower preference value.";
    reference
      "RFC 8665: OSPF Extensions for Segment Routing
       (Section 3.4)";
    container srms-preference-tlv {
      description
        "SRMS Preference TLV.";
      leaf preference {
        type uint8;
        description
          "SRMS preference TLV, value from 0 to 255 with
           255 being the most preferred.";
      }
    }
  }

  grouping ospfv3-prefix-sid-sub-tlvs {
    description
      "OSPFv3 Prefix Segment ID (SID) sub-TLVs.";
    reference
      "RFC 8666: OSPFv3 Extensions for Segment Routing
       (Section 6)";
    container prefix-sid-sub-tlvs {
      description
        "Prefix SID sub-TLV.";
      list prefix-sid-sub-tlv {
        description
          "Prefix SID sub-TLV.";
        container ospfv3-prefix-sid-flags {
          leaf-list flag {
            type identityref {
              base prefix-sid-flag;
            }
            description
              "Prefix SID sub-TLV flags.";
          }
          description
            "Segment Identifier (SID) Flags.";
        }
        leaf algorithm {
          type identityref {
            base sr-cmn:prefix-sid-algorithm;
          }
          description
            "Algorithm associated with the prefix-SID.";
        }
        uses sid-tlv-encoding;
      }
    }
  }

  grouping ospfv3-extended-prefix-range-tlvs {
    description
      "OSPFv3 Extended prefix range TLV grouping.";
    reference
      "RFC 8666: OSPFv3 Extensions for Segment Routing
       (Section 5)";
    container ospfv3-extended-prefix-range-tlvs {
      description
        "List of extended prefix range TLVs.";
      list extended-prefix-range-tlv {
        description
          "Range of prefixes.";
        leaf prefix-length {
          type uint8;
          description
            "Length of prefix in bits.";
        }
        leaf af {
          type iana-rt-types:address-family;
          description
            "Address family for the prefix.";
        }
        leaf range-size {
          type uint16;
          description
            "Number of prefixes covered by the advertisement.
             The return of a value of zero would indicate an error.";
        }
        leaf prefix {
          type inet:ip-prefix;
          description
            "IPv4 or IPv6 prefix.";
        }
        uses ospfv3-prefix-sid-sub-tlvs;
        uses ospf:unknown-tlvs;
      }
    }
  }

  grouping ospfv3-adj-sid-sub-tlvs {
    description
      "OSPFv3 Adj-SID sub-TLV grouping.";
    reference
      "RFC 8666: OSPFv3 Extensions for Segment Routing
       (Section 7)";
    container adj-sid-sub-tlvs {
      description
        "Adj-SID optional sub-TLVs.";
      list adj-sid-sub-tlv {
        description
          "List of Adj-SID sub-TLVs.";
        container adj-sid-flags {
          leaf-list flag {
            type identityref {
              base adj-sid-flag;
            }
            description
              "Adj-SID sub-tlv flags.";
          }
          description
            "Adj-sid sub-tlv flags.";
        }
        leaf weight {
          type uint8;
          description
            "Weight used for load-balancing.";
        }
        uses sid-tlv-encoding;
      }
    }
  }

  grouping ospfv3-lan-adj-sid-sub-tlvs {
    description
      "OSPFv3 LAN Adj-SID sub-TLV grouping.";
    reference
      "RFC 8666: OSPFv3 Extensions for Segment Routing
       (Section 7)";
    container lan-adj-sid-sub-tlvs {
      description
        "LAN Adj-SID optional sub-TLVs.";
      list lan-adj-sid-sub-tlv {
        description
          "List of LAN Adj-SID sub-TLVs.";
        container lan-adj-sid-flags {
          leaf-list flag {
            type identityref {
              base adj-sid-flag;
            }
            description
              "LAN Adj-SID sub-TLV flags.";
          }
          description
            "LAN Adj-SID sub-TLV flags.";
        }
        leaf weight {
          type uint8;
          description
            "Weight used for load-balancing.";
        }
        leaf neighbor-router-id {
          type rt-types:router-id;
          description
            "Neighbor router ID.";
        }
        uses sid-tlv-encoding;
      }
    }
  }

  /*
   * Augmentations for OSPF SR MPLS Configuration (read-write)
   * data nodes.
   */

  augment "/rt:routing/rt:control-plane-protocols"
        + "/rt:control-plane-protocol/ospf:ospf" {
    when "derived-from(/rt:routing/rt:control-plane-protocols/"
       + "rt:control-plane-protocol/rt:type, 'ospf:ospf')" {
      description
        "This augments the OSPF routing protocol when used.";
    }
    description
      "This augments the OSPF protocol configuration with segment
       routing over the MPLS data plane. The following semantic
       validation be performed for the configuration data:
        - Assure the binding policies prefixes do not overlapp.";
    reference
      "RFC 9020 - YANG Data Model for Segment Routing";
    uses sr-mpls:sr-control-plane;
    container protocol-srgb {
      if-feature "sr-mpls:protocol-srgb";
      uses sr-cmn:srgb;
      description
        "Per-protocol SRGB.";
    }
  }

  augment "/rt:routing/rt:control-plane-protocols/"
        + "rt:control-plane-protocol/ospf:ospf/"
        + "ospf:areas/ospf:area" {
    when "derived-from(/rt:routing/rt:control-plane-protocols/"
       + "rt:control-plane-protocol/rt:type, 'ospf:ospf') and "
       + "/rt:routing/rt:control-plane-protocols"
       + "/rt:control-plane-protocol/ospf:ospf"
       + "/ospf-sr-mpls:segment-routing/"
       + "ospf-sr-mpls:enabled = 'true'" {
      description
        "This augments the OSPF area configuration when segment
         routing is enabled at the OSPF instance level.";
    }
    container segment-routing {
      presence "When present segment routing over MPLS is enabled
                for the area.";
      description
        "OSPF area level segment routing configuration. Enable
         segment routing over MPLS on all interfaces and enables
         advertisement of Link State Advertisements (LSAs) and TLVs
         supporting segment routing over MPLS";
    }
    description
      "This augments the OSPF protocol area configuration with
       segment routing.";
  }

  augment "/rt:routing/rt:control-plane-protocols/"
        + "rt:control-plane-protocol/ospf:ospf/"
        + "ospf:areas/ospf:area/ospf:interfaces/ospf:interface" {
    when "derived-from(/rt:routing/rt:control-plane-protocols/"
       + "rt:control-plane-protocol/rt:type, 'ospf:ospf') and "
       + "/rt:routing/rt:control-plane-protocols/"
       + "rt:control-plane-protocol/ospf:ospf/"
       + "ospf:areas/ospf:area/ospf-sr-mpls:segment-routing" {
      description
        "This augments the OSPF interface configuration when used.";
    }
    description
      "This augments the OSPF protocol interface
       configuration with segment routing.";
    reference
      "RFC 9020 - YANG Data Model for Segment Routing";
    uses sr-mpls:igp-interface {
      augment "segment-routing" {
        leaf enabled {
          type boolean;
          default "true";
          description
            "Enable or disable segment-routing over MPLS at the OSPF
             interface level when segment routing over MPLS is
             enabled at the area level.";
        }
        description
          "Allow explicit enablement of segment routing";
      }
      augment "segment-routing/adjacency-sid/adj-sids" {
        when "((../../../ospf:interface-type = 'broadcast') or
              (../../../ospf:interface-type = 'non-broadcast'))" {
          description
            "This augments broadcast and non-broadcast multi-access
             interface segment routing interface configuration.";
        }
        description
          "This augments LAN interface adj-sid with neighbor-id.";
        leaf neighbor-id {
          type inet:ip-address;
          mandatory true;
          description
            "Neighbor's Router ID, IPv4 address, or IPv6 address.
             Specification is optional and, if specified, SHOULD
             specify a neighbor reachable via the interface.";
        }
      }
    }
  }

  augment "/rt:routing/rt:control-plane-protocols/"
        + "rt:control-plane-protocol/ospf:ospf/"
        + "ospf:areas/ospf:area/ospf:interfaces/ospf:interface/"
        + "ospf:fast-reroute/ospf:lfa" {
    when "derived-from(/rt:routing/rt:control-plane-protocols/"
       + "rt:control-plane-protocol/rt:type, 'ospf:ospf')" {
      description
        "This augments the OSPF routing protocol when used.";
    }
    description
      "This augments the OSPF protocol IP-FRR with TI-LFA.";
    container ti-lfa {
      if-feature "ti-lfa";
      description
        "Topology-Independent Loop Free Alternate
         (TI-LFA) support.";
      reference
        "draft-ietf-rtgwg-segment-routing-ti-lfa:
         Topology-Independent Fast Reroute using Segment Routing";
      leaf enabled {
        type boolean;
        default "false";
        description
          "Enable TI-LFA computation.";
      }
      container selection-tie-breakers {
        container node-protection {
          presence "Presence of container enables the node
                    protection tie-breaker.";
          leaf priority {
            type uint8;
            default "128";
            description
              "Priority for node protection tie-breaker with
               a lower priority being more preferred. By default,
               the priority is in the middle of the priority range.";
          }
          description
            "Enable node protection as a TI-LFA path
             selection tie-breaker. A path providing node
             protection will be selected over one that
             doesn't provide node protection.";
        }
        container srlg-disjoint {
          presence "Presence of container enables the SRLG
                    disjoint tie-breaker";
          leaf priority {
            type uint8;
            default "128";
            description
              "Priority for SRLG disjoint tie-breaker with
               a lower priority being more preferred. By default,
               the priority is in the middle of the priority range.";
          }
          description
            "Enable SRLG (Sharsed Resource Link Group)
             disjoint as a TI-LFA path selection tie-breaker.
             A path providing node a disjoint path for SRLG
             links from the primary path will be selected over
             one that doesn't provide an SRLG disjoint path.";
        }
        description
          "Configure path selection tie-breakers and their
           respective priorities for the TI-LFA computation.
           multiple tie-breakers and priorities configured may
           be configured.";
      }
    }
  }

  augment "/rt:routing/rt:control-plane-protocols/"
        + "rt:control-plane-protocol/ospf:ospf/"
        + "ospf:areas/ospf:area/ospf:interfaces/ospf:interface/"
        + "ospf:fast-reroute/ospf:lfa/ospf:remote-lfa" {
    when "derived-from(/rt:routing/rt:control-plane-protocols/"
       + "rt:control-plane-protocol/rt:type, 'ospf:ospf')" {
      description
        "This augments the OSPF routing protocol when used.";
    }
    description
      "This augments the OSPF protocol IP-FRR with remote LFA.";
    reference
      "draft-ietf-rtgwg-segment-routing-ti-lfa:
       Topology-Independent Fast Reroute using Segment Routing";
    leaf use-segment-routing-path {
      if-feature "remote-lfa-sr";
      type boolean;
      default "false";
      description
        "Force remote LFA to use segment routing path instead of LDP
         path. The value of this leaf is in effect only when
         remote-lfa is enabled.";
    }
  }

  /*
   * Augmentations for read-only data nodes corresponding to Segment
   * Routing encodings in OSPFv2 and OSPFv3 Link State Advertisements
   * (LSAs) in OSPF Link State Databases (LSDBs) at the instance,
   * area, and interface level.
   */
  /* Augmentations for OSPFv2 LSAs. */

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-prefix-opaque" {
    when "derived-from(/rt:routing/rt:control-plane-protocols/"
       + "rt:control-plane-protocol/rt:type, 'ospf:ospfv2')" {
      description
        "This augmentation is only valid for OSPFv2.";
    }
    description
      "SR Extended Prefix Range TLV in OSPFv2 Type 10 (area-scoped)
       Extended Prefix Opaque LSAs.";
    reference
      "RFC 8665: OSPF Extensions for Segment Routing
       (Section 4)";
    uses ospfv2-extended-prefix-range-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/"
        + "ospf:extended-prefix-opaque" {
    when "derived-from(/rt:routing/rt:control-plane-protocols/"
       + "rt:control-plane-protocol/rt:type, 'ospf:ospfv2')" {
      description
        "This augmentation is only valid for OSPFv2.";
    }
    description
      "SR Extended Prefix Range TLV in OSPFv2 Type 11 (AS-scoped)
       Extended Prefix Opaque LSAs.";
    reference
      "RFC 8665: OSPF Extensions for Segment Routing
       (Section 4)";
    uses ospfv2-extended-prefix-range-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-prefix-opaque/ospf:extended-prefix-tlv" {
    when "derived-from(/rt:routing/rt:control-plane-protocols/"
       + "rt:control-plane-protocol/rt:type, 'ospf:ospfv2')" {
      description
        "This augmentation is only valid for OSPFv2.";
    }
    description
      "SR Prefix-SID sub-TLVs for OSPFv2 Extended Prefix TLVs
       in OSPFv2 Type 10 (area-scoped) Extended Prefix Opaque LSAs.";
    uses ospfv2-prefix-sid-sub-tlvs;
    reference
      "RFC 8665: OSPF Extensions for Segment Routing
        (Section 5)";
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/"
        + "ospf:extended-prefix-opaque/ospf:extended-prefix-tlv" {
    when "derived-from(/rt:routing/rt:control-plane-protocols/"
       + "rt:control-plane-protocol/rt:type, 'ospf:ospfv2')" {
      description
        "This augmentation is only valid for OSPFv2.";
    }
    description
      "SR Prefix-SID sub-TLVs for OSPFv2 Extended Prefix TLVs
       in OSPFv2 Type 11 (AS-scoped) Extended Prefix Opaque LSAs.";
    reference
      "RFC 8665: OSPF Extensions for Segment Routing
        (Section 5)";
    uses ospfv2-prefix-sid-sub-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/"
        + "ospf:extended-link-opaque/ospf:extended-link-tlv" {
    when "derived-from(/rt:routing/rt:control-plane-protocols/"
       + "rt:control-plane-protocol/rt:type, 'ospf:ospfv2')" {
      description
        "This augmentation is only valid for OSPFv2.";
    }
    description
      "SR TLVs for OSPFv2 Extended Link TLV in OSPFv2 Type 10
       (area-scoped) Extended Link Opaque LSAs.";
    reference
      "RFC 8665: OSPF Extensions for Segment Routing
        (Section 6)";
    uses ospfv2-adj-sid-sub-tlvs;
    uses ospfv2-lan-adj-sid-sub-tlvs;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv2/"
        + "ospf:ospfv2/ospf:body/ospf:opaque/ospf:ri-opaque" {
    when "derived-from(/rt:routing/rt:control-plane-protocols/"
       + "rt:control-plane-protocol/rt:type, 'ospf:ospfv2')" {
      description
        "This augmentation is only valid for OSPFv2.";
    }
    description
      "SR TLVs for OSPFv2 Router Information Type 10 (area-scoped)
       Opaque LSAs";
    reference
      "RFC 8665: OSPF Extensions for Segment Routing
        (Section 3)";
    uses sr-algorithm-tlv;
    uses sid-range-tlvs;
    uses local-block-tlvs;
    uses srms-preference-tlv;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv2/"
        + "ospf:ospfv2/ospf:body/ospf:opaque/ospf:ri-opaque" {
    when "derived-from(/rt:routing/rt:control-plane-protocols/"
       + "rt:control-plane-protocol/rt:type, 'ospf:ospfv2')" {
      description
        "This augmentation is only valid for OSPFv2.";
    }
    description
      "SR TLVs for OSPFv2 Router Information Type 11 (AS-scoped)
       Opaque LSAs";
    reference
      "RFC 8665: OSPF Extensions for Segment Routing
        (Section 3)";
    uses sr-algorithm-tlv;
    uses sid-range-tlvs;
    uses local-block-tlvs;
    uses srms-preference-tlv;
  }

  /* Augmentations for OSPFv3 LSAs. */

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospf:router-information" {
    when "derived-from(/rt:routing/rt:control-plane-protocols/"
       + "rt:control-plane-protocol/rt:type, 'ospf:ospfv3')" {
      description
        "This augmentation is only valid for OSPFv3.";
    }
    description
      "SR-specific TLVs for OSPFv3 Router Information LSA
       (area-scoped).";
    reference
      "RFC 8666: OSPFv3 Extensions for Segment Routing
       (Section 4)";
    uses sr-algorithm-tlv;
    uses sid-range-tlvs;
    uses local-block-tlvs;
    uses srms-preference-tlv;
  }

  augment "/rt:routing/"
        + "rt:control-plane-protocols/rt:control-plane-protocol/"
        + "ospf:ospf/ospf:areas/"
        + "ospf:area/ospf:database/"
        + "ospf:area-scope-lsa-type/ospf:area-scope-lsas/"
        + "ospf:area-scope-lsa/ospf:version/ospf:ospfv3/"
        + "ospf:ospfv3/ospf:body/ospf:router-information" {
    when "derived-from(/rt:routing/rt:control-plane-protocols/"
       + "rt:control-plane-protocol/rt:type, 'ospf:ospfv3')" {
      description
        "This augmentation is only valid for OSPFv3.";
    }
    description
      "SR-specific TLVs for OSPFv3 Router Information LSA
       (AS-scoped).";
    reference
      "RFC 8666: OSPFv3 Extensions for Segment Routing
       (Section 4)";
    uses sr-algorithm-tlv;
    uses sid-range-tlvs;
    uses local-block-tlvs;
    uses srms-preference-tlv;
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-intra-area-prefix" {
    when "derived-from(/rt:routing/rt:control-plane-protocols/"
       + "rt:control-plane-protocol/rt:type, 'ospf:ospfv3')" {
      description
        "This augmentation is only valid for OSPFv3.";
    }
    uses ospfv3-extended-prefix-range-tlvs;
    description
      "SR Extended Prefix Range TLVs in OSPFv3
       E-Intra-Area-Prefix LSAs.";
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-inter-area-prefix" {
    when "derived-from(/rt:routing/rt:control-plane-protocols/"
       + "rt:control-plane-protocol/rt:type, 'ospf:ospfv3')" {
      description
        "This augmentation is only valid for OSPFv3.";
    }
    description
      "SR Extended Prefix Range TLVs in OSPFv3
       E-Inter-Area-Prefix LSAs.";
    reference
      "RFC 8666: OSPFv3 Extensions for Segment Routing
       (Section 5)";
    uses ospfv3-extended-prefix-range-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospfv3-e-lsa:e-as-external" {
    when "derived-from(/rt:routing/rt:control-plane-protocols/"
       + "rt:control-plane-protocol/rt:type, 'ospf:ospfv3')" {
      description
        "This augmentation is only valid for OSPFv3.";
    }
    description
      "SR Extended Prefix Range TLVs in OSPFv3 E-AS-External LSAs.";
    reference
      "RFC 8666: OSPFv3 Extensions for Segment Routing
       (Section 5)";
    uses ospfv3-extended-prefix-range-tlvs;
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-nssa" {
    when "derived-from(/rt:routing/rt:control-plane-protocols/"
       + "rt:control-plane-protocol/rt:type, 'ospf:ospfv3')" {
      description
        "This augmentation is only valid for OSPFv3.";
    }
    description
      "SR Extended Prefix Range TLVs in OSPFv3 E-NSSA LSAs.";
    reference
      "RFC 8666: OSPFv3 Extensions for Segment Routing
       (Section 5)";
    uses ospfv3-extended-prefix-range-tlvs;
  }

  augment "/rt:routing/"
        + "rt:control-plane-protocols/rt:control-plane-protocol/"
        + "ospf:ospf/ospf:areas/ospf:area/ospf:interfaces/"
        + "ospf:interface/"
        + "ospf:database/ospf:link-scope-lsa-type/"
        + "ospf:link-scope-lsas/ospf:link-scope-lsa/"
        + "ospf:version/ospf:ospfv3/ospf:ospfv3/"
        + "ospf:body/ospfv3-e-lsa:e-link/"
        + "ospfv3-e-lsa:e-link-tlvs/ospfv3-e-lsa:intra-prefix-tlv/"
        + "ospfv3-e-lsa:sub-tlvs" {
    when "derived-from(/rt:routing/rt:control-plane-protocols/"
       + "rt:control-plane-protocol/rt:type, 'ospf:ospfv3')" {
      description
        "This augmentation is only valid for OSPFv3.";
    }
    description
      "SR Prefix-SID Sub-TLV in OSPFv3 Intra-Area
       Prefix TLV for OSPFv3 E-Link LSAs.";
    reference
      "RFC 8666: OSPFv3 Extensions for Segment Routing
       (Section 6)";
    uses ospfv3-prefix-sid-sub-tlvs;
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-intra-area-prefix/"
        + "ospfv3-e-lsa:e-intra-prefix-tlvs/"
        + "ospfv3-e-lsa:intra-prefix-tlv/"
        + "ospfv3-e-lsa:sub-tlvs" {
    when "derived-from(/rt:routing/rt:control-plane-protocols/"
       + "rt:control-plane-protocol/rt:type, 'ospf:ospfv3')" {
      description
        "This augmentation is only valid for OSPFv3
         E-Router LSAs";
    }
    description
      "SR Prefix-SID Sub-TLV in OSPFv3 Intra-Area
       Prefix TLV for OSPFv3 E-Intra-Area-Prefix LSAs.";
    reference
      "RFC 8666: OSPFv3 Extensions for Segment Routing
       (Section 6)";
    uses ospfv3-prefix-sid-sub-tlvs;
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-inter-area-prefix/"
        + "ospfv3-e-lsa:e-inter-prefix-tlvs/"
        + "ospfv3-e-lsa:inter-prefix-tlv/"
        + "ospfv3-e-lsa:sub-tlvs" {
    when "derived-from(/rt:routing/rt:control-plane-protocols/"
       + "rt:control-plane-protocol/rt:type, 'ospf:ospfv3')" {
      description
        "This augmentation is only valid for OSPFv3.";
    }
    description
      "SR Prefix-SID Sub-TLV in OSPFv3 Link-Scoped Intra-Area
       Prefix TLV for OSPFv3 E-Inter-Area-Prefix LSAs.";
    reference
      "RFC 8666: OSPFv3 Extensions for Segment Routing
       (Section 6)";
    uses ospfv3-prefix-sid-sub-tlvs;
  }

  augment "/rt:routing/"
        + "rt:control-plane-protocols/rt:control-plane-protocol/"
        + "ospf:ospf/ospf:database/"
        + "ospf:as-scope-lsa-type/ospf:as-scope-lsas/"
        + "ospf:as-scope-lsa/ospf:version/ospf:ospfv3/"
        + "ospf:ospfv3/ospf:body/ospfv3-e-lsa:e-as-external/"
        + "ospfv3-e-lsa:e-external-tlvs/"
        + "ospfv3-e-lsa:external-prefix-tlv/"
        + "ospfv3-e-lsa:sub-tlvs" {
    when "derived-from(/rt:routing/rt:control-plane-protocols/"
       + "rt:control-plane-protocol/rt:type, 'ospf:ospfv3')" {
      description
        "This augmentation is only valid for OSPFv3.";
    }
    description
      "SR Prefix-SID Sub-TLV in OSPFv3 External Prefix TLV
       for OSPFv3 E-AS-External LSAs.";
    reference
      "RFC 8666: OSPFv3 Extensions for Segment Routing
       (Section 6)";
    uses ospfv3-prefix-sid-sub-tlvs;
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-nssa/"
        + "ospfv3-e-lsa:e-external-tlvs/"
        + "ospfv3-e-lsa:external-prefix-tlv/"
        + "ospfv3-e-lsa:sub-tlvs" {
    when "derived-from(/rt:routing/rt:control-plane-protocols/"
       + "rt:control-plane-protocol/rt:type, 'ospf:ospfv3')" {
      description
        "This augmentation is only valid for OSPFv3.";
    }
    description
      "SR Prefix-SID Sub-TLV in OSPFv3 External Prefix TLV
       for OSPFv3 E-NSSA LSAs.";
    reference
      "RFC 8666: OSPFv3 Extensions for Segment Routing
       (Section 6)";
    uses ospfv3-prefix-sid-sub-tlvs;
  }

  augment "/rt:routing/"
        + "rt:control-plane-protocols/rt:control-plane-protocol/"
        + "ospf:ospf/ospf:areas/ospf:area/ospf:database/"
        + "ospf:area-scope-lsa-type/ospf:area-scope-lsas/"
        + "ospf:area-scope-lsa/ospf:version/ospf:ospfv3/"
        + "ospf:ospfv3/ospf:body/ospfv3-e-lsa:e-router/"
        + "ospfv3-e-lsa:e-router-tlvs/ospfv3-e-lsa:link-tlv/"
        + "ospfv3-e-lsa:sub-tlvs" {
    when "derived-from(/rt:routing/rt:control-plane-protocols/"
       + "rt:control-plane-protocol/rt:type, 'ospf:ospfv3')" {
      description
        "This augmentation is only valid for OSPFv3
         E-Router LSAs";
    }
    description
      "SR Sub-TLVs in OSPFv3 link-tlv for OSPFv3 E-Router LSAs";
    reference
      "RFC 8666: OSPFv3 Extensions for Segment Routing
       (Section 7)";
    uses ospfv3-adj-sid-sub-tlvs;
    uses ospfv3-lan-adj-sid-sub-tlvs;
  }
}
